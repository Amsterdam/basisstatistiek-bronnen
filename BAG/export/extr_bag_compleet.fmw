FME workspace extr_bag_compleet.fmw

Parameters:
- SourceDataset_ORACLE8I_DB = DBIGMP01   # Source Oracle Non-spatial Service
- DestDataset_CSV = G:\OIS\Projecten\lopende Projecten\17004 Stand Onderhoud en Ontwikkeling\17004.XX Bronbeheer\bag_20171009   # Destination Comma Separated Value (CSV) Directory

Readers:
- ORACLE8I_DB_1: ORACLE8I_DB from $(SourceDataset_ORACLE8I_DB)

Writers:
- CSV_1: CSV to $(DestDataset_CSV)

Note: SQLCreator_woonplaats
SQLCreator_woonplaats
    ORACLE_NONSPATIAL_REMOVE_SCHEMA_QUALIFIER = NO
    DATASET = DBIGMP01
    FORMAT = ORACLE_NONSPATIAL
    ORACLE_NONSPATIAL_PERSISTENT_CONNECTION = YES
    ORACLE_NONSPATIAL_SHOW_SYSTEM_TABLES = NO
    ORACLE_NONSPATIAL_QUERY_FEATURE_TYPES_FOR_MERGE_FILTERS = Yes
    SQL_STATEMENT:
      select to_char(sysdate,'yyyymmdd') as datum_export
      ,      wps_id
      ,      gme_id
      ,      woonplaatsnaam
      ,      woonplaatscode
      ,      to_char(documentdatum_mutatie,'yyyymmddHH24MI:ss') documentdatum_mutatie
      ,      documentnummer_mutatie
      ,      to_char(ingangsdatum_geldigheid,'yyyymmddHH24MI:ss') ingangsdatum_geldigheid
      ,      to_char(einddatum_geldigheid,'yyyymmddHH24MI:ss')  einddatum_geldigheid
      ,      to_char(mutatiedatum,'yyyymmddHH24MI:ss') mutatiedatum
      ,      to_char(opvoerdatum,'yyyymmddHH24MI:ss') opvoerdatum
      ,      objectcyclusnr
      ,      sdo_util.TO_WKTGEOMETRY(geometrie) wktgeometrie
      from   gegmag.gvi_woonplaats_data
    ORACLE_NONSPATIAL_USE_UNIFIED_DATE_ATTRS = YES
    EXPOSED_ATTRIBUTE_LIST = DATUM_EXPORT,WPS_ID,GME_ID,WOONPLAATSNAAM,WOONPLAATSCODE,EINDDATUM_GELDIGHEID,INGANGSDATUM_GELDIGHEID,MUTATIEDATUM,OBJECTCYCLUSNR,OPVOERDATUM,WKTGEOMETRIE
    ORACLE_NONSPATIAL_SERVER_TYPE = ORACLE8i
    ORACLE_NONSPATIAL_NAMED_CONNECTION = DBIGMP01
    RESULT -> woonplaats (writer CSV_1)
Note: woonplaats: BAG_compleet [CSV]
woonplaats (writer CSV_1)
    attributes: DATUM_EXPORT auto, WPS_ID auto, GME_ID auto, WOONPLAATSNAAM auto, WOONPLAATSCODE auto, EINDDATUM_GELDIGHEID auto, INGANGSDATUM_GELDIGHEID auto, MUTATIEDATUM auto, OBJECTCYCLUSNR auto, OPVOERDATUM auto, WKTGEOMETRIE auto
Note: SQLCreator_opr
Note: SQLCreator_opr
SQLCreator_opr
    DATASET = DBIGMP01
    FORMAT = ORACLE_SPATIAL
    ORACLE_SPATIAL_PERSISTENT_CONNECTION = YES
    ORACLE_SPATIAL_USE_UNIFIED_DATE_ATTRS = YES
    ORACLE_SPATIAL_SHOW_SYSTEM_TABLES = NO
    SQL_STATEMENT:
      select to_number(orm.bag_identificatiecode) as bag_identificatiecode
      ,      ore.ore_id
      ,      ore.wps_id
      ,      to_number(ore.straatcode)   as straatcode
      ,      to_number(ore.typering_dmn) as typering_dmn
      ,      ore.naam
      ,      ore.naam_nen
      ,      ore.naam_ptt
      ,      ore.zoeknaam
      ,      to_number(ore.statuscode)   as statuscode
      ,      to_char(ore.ingangsdatum_geldigheid,'YYYYMMDD') as ingangsdatum_geldigheid
      ,      to_char(ore.einddatum_geldigheid,'YYYYMMDD')    as einddatum_geldigheid
      ,      to_char(ore.opvoerdatum,'YYYYMMDDHH24MMSS')     as opvoerdatum
      ,      ore.indauthentiek
      ,      ore.indgeconstateerd
      ,      ore.indinonderzoek
      ,      ore.objectcyclusnr
      from   gegmag.gvi_openbare_ruimte_data ore
      join   gegmag.gvi_openbare_ruimte orm on (ore.ore_id=orm.id)
    ORACLE_SPATIAL_QUERY_FEATURE_TYPES_FOR_MERGE_FILTERS = Yes
    ORACLE_SPATIAL_SERVER_TYPE = ORACLE8i
    EXPOSED_ATTRIBUTE_LIST = BAG_IDENTIFICATIECODE,ORE_ID,WPS_ID,STRAATCODE,TYPERING_DMN,NAAM,NAAM_NEN,NAAM_PTT,ZOEKNAAM,STATUSCODE,INGANGSDATUM_GELDIGHEID,EINDDATUM_GELDIGHEID,OPVOERDATUM,INDAUTHENTIEK,INDGECONSTATEERD,INDINONDERZOEK,OBJECTCYCLUSNR
    ORACLE_SPATIAL_REMOVE_SCHEMA_QUALIFIER = NO
    ORACLE_SPATIAL_NAMED_CONNECTION = DBIGMP01
    RESULT -> openbare_ruimte (writer CSV_1)
Note: openbare_ruimte: BAG_compleet [CSV]
openbare_ruimte (writer CSV_1)
    attributes: BAG_IDENTIFICATIECODE auto, ORE_ID auto, WPS_ID auto, STRAATCODE auto, TYPERING_DMN auto, NAAM auto, NAAM_NEN auto, NAAM_PTT auto, ZOEKNAAM auto, STATUSCODE auto, INGANGSDATUM_GELDIGHEID auto, EINDDATUM_GELDIGHEID auto, OPVOERDATUM auto, INDAUTHENTIEK auto, INDGECONSTATEERD auto, INDINONDERZOEK auto, OBJECTCYCLUSNR auto
Note: SQLCreator_verblijfsobject
SQLCreator_verblijfsobject
    DATASET = DBIGMP01
    FORMAT = ORACLE_SPATIAL
    ORACLE_SPATIAL_PERSISTENT_CONNECTION = YES
    COORDSYS = EPSG:28992
    ORACLE_SPATIAL_USE_UNIFIED_DATE_ATTRS = YES
    ORACLE_SPATIAL_SHOW_SYSTEM_TABLES = NO
    SQL_STATEMENT:
      select
            to_number(vtm.bag_identificatiecode)		    as lv_bag_vot_id
      ,     vot.vot_id				            	    as vot_diva_id
      ,     vot.brt_id                                    as brt_id
      ,     vot.geometrie                                 as geometrie -- in FME vervangen door WKT
      ,     to_number(vot.gebruiksdoel_dmn)			    as gebruiksdoel
      ,     vot.oppervlakte                               as oppervlakte
      ,     to_number(vot.statuscode)                     as statuscode
      ,     vot.redenopvoercode		                    as redenopvoer
      ,     vot.redenafvoercode		                    as redenafvoer
      ,     vot.aantal_verhuurbare_eenheden	            as aantal_vhe
      ,     to_number(vot.liggingcode)                    as liggingcode
      ,     to_number(vot.gebruikscode)				    as feitelijkgebruik
      ,     to_number(vot.aantal_bouwlagen)               as aantal_bouwlagen
      ,     vot.type_woonobject_dmn		                as object_type
      ,     vot.eigendomsverhoudingcode	                as eigendomsverhouding
      ,     vot.aantal_kamers                             as aantal_kamers
      ,     to_number(vot.toegangscode)                   as toegangscode
      ,     to_number(vot.locatieingangcode)              as locatieingangcode
      ,     to_number(vot.bouwlaagtoegang)                as bouwlaagtoegang
      ,     to_char(vot.ingangsdatum_cyclus,'YYYYMMDD')	as geldig_op
      ,     to_char(vot.opvoerdatum,'YYYYMMDDHH24MMSS')	as kennisgegeven_op
      ,     vot.objectcyclusnr
      ,     vot.indauthentiek
      ,     vot.indgeconstateerd
      ,     vot.indinonderzoek
      from   gegmag.gvi_verblijfsobject_data vot
      join   gegmag.gvi_verblijfsobject vtm on (vot.vot_id=vtm.id)
    ORACLE_SPATIAL_QUERY_FEATURE_TYPES_FOR_MERGE_FILTERS = Yes
    ORACLE_SPATIAL_SERVER_TYPE = ORACLE8i
    EXPOSED_ATTRIBUTE_LIST = LV_BAG_VOT_ID,VOT_DIVA_ID,BRT_ID,GEBRUIKSDOEL,OPPERVLAKTE,STATUSCODE,REDENOPVOER,REDENAFVOER,AANTAL_VHE,LIGGINGCODE,FEITELIJKGEBRUIK,AANTAL_BOUWLAGEN,OBJECT_TYPE,EIGENDOMSVERHOUDING,AANTAL_KAMERS,TOEGANGSCODE,LOCATIEINGANGCODE,BOUWLAAGTOEGANG,GELDIG_OP,KENNISGEGEVEN_OP,OBJECTCYCLUSNR,INDAUTHENTIEK,INDGECONSTATEERD,INDINONDERZOEK
    ORACLE_SPATIAL_REMOVE_SCHEMA_QUALIFIER = NO
    ORACLE_SPATIAL_NAMED_CONNECTION = DBIGMP01
    RESULT -> GeometryExtractor_verblijfsobject
Note: GeometryExtractor_verblijfsobject
GeometryExtractor_verblijfsobject
    KIND_LONG = OGC Well Known Text
    OGC_WKT_PRECISION_DISPLAY = Shortened 64-bit
    REMOVE_GEOMETRY = Yes
    ATTR = geometrie_wkt
    OGCVERSION = 1.1
    -> verblijfsobject (writer CSV_1)
Note: verblijfsobject: BAG_compleet [CSV]
verblijfsobject (writer CSV_1)
    attributes: LV_BAG_VOT_ID text, VOT_DIVA_ID text, BRT_ID text, geometrie_wkt auto, GEBRUIKSDOEL auto, OPPERVLAKTE text, STATUSCODE text, REDENOPVOER auto, REDENAFVOER auto, AANTAL_VHE auto, LIGGINGCODE text, FEITELIJKGEBRUIK auto, AANTAL_BOUWLAGEN text, OBJECT_TYPE auto, EIGENDOMSVERHOUDING auto, AANTAL_KAMERS text, TOEGANGSCODE text, LOCATIEINGANGCODE text, BOUWLAAGTOEGANG text, GELDIG_OP auto, KENNISGEGEVEN_OP auto, OBJECTCYCLUSNR text, INDAUTHENTIEK text, INDGECONSTATEERD text, INDINONDERZOEK text
Note: SQLCreator_nummeraanduiding
SQLCreator_nummeraanduiding
    ORACLE_NONSPATIAL_REMOVE_SCHEMA_QUALIFIER = NO
    DATASET = DBIGMP01
    FORMAT = ORACLE_NONSPATIAL
    ORACLE_NONSPATIAL_PERSISTENT_CONNECTION = YES
    ORACLE_NONSPATIAL_SHOW_SYSTEM_TABLES = NO
    ORACLE_NONSPATIAL_QUERY_FEATURE_TYPES_FOR_MERGE_FILTERS = Yes
    SQL_STATEMENT:
      select
              to_number(mnum.bag_identificatiecode) 	as lv_bag_nag_id
      ,       num.nag_id
      ,       num.ore_id
      ,       num.huisnummer
      ,       num.huisletter
      ,       num.huisnummertoevoeging
      ,       num.postcode
      ,       to_number(num.type_adresseerbaar_object_dmn)	as object_type
      ,       to_number(num.statuscode) as statuscode
      ,       to_char(num.ingangsdatum_cyclus,'YYYYMMDD')	as geldig_op
      ,       to_char(num.opvoerdatum,'YYYYMMDDHH24MMSS')	as kennisgegeven_op
      ,       num.adrescyclusnr
      ,       num.indauthentiek
      ,       num.indgeconstateerd
      ,       num.indinonderzoek
      from   gegmag.gvi_nummeraanduiding_data num
      join   gegmag.gvi_nummeraanduiding mnum on (num.nag_id=mnum.id)
    ORACLE_NONSPATIAL_USE_UNIFIED_DATE_ATTRS = YES
    EXPOSED_ATTRIBUTE_LIST = LV_BAG_NAG_ID,NAG_ID,ORE_ID,HUISNUMMER,HUISLETTER,HUISNUMMERTOEVOEGING,POSTCODE,OBJECT_TYPE,STATUSCODE,GELDIG_OP,KENNISGEGEVEN_OP,ADRESCYCLUSNR,INDAUTHENTIEK,INDGECONSTATEERD,INDINONDERZOEK
    ORACLE_NONSPATIAL_SERVER_TYPE = ORACLE8i
    ORACLE_NONSPATIAL_NAMED_CONNECTION = DBIGMP01
    RESULT -> nummeraanduiding (writer CSV_1)
Note: nummeraanduiding: BAG_compleet [CSV]
nummeraanduiding (writer CSV_1)
    attributes: LV_BAG_NAG_ID text, NAG_ID text, ORE_ID text, HUISNUMMER text, HUISLETTER text, HUISNUMMERTOEVOEGING text, POSTCODE text, OBJECT_TYPE auto, STATUSCODE text, GELDIG_OP auto, KENNISGEGEVEN_OP auto, ADRESCYCLUSNR text, INDAUTHENTIEK text, INDGECONSTATEERD text, INDINONDERZOEK text
Note: SQLCreator_pand
SQLCreator_pand
    DATASET = DBIGMP01
    FORMAT = ORACLE_SPATIAL
    ORACLE_SPATIAL_PERSISTENT_CONNECTION = YES
    COORDSYS = EPSG:28992
    ORACLE_SPATIAL_USE_UNIFIED_DATE_ATTRS = YES
    ORACLE_SPATIAL_SHOW_SYSTEM_TABLES = NO
    SQL_STATEMENT:
      select to_number(pdm.bag_identificatiecode)  as bag_identificatiecode
      ,      pnd_id
      ,      bbk_id
      ,      oorspronkelijk_bouwjaar
      ,      statuscode
      ,      laagste_bouwlaag
      ,      hoogste_bouwlaag
      ,      to_char(ingangsdatum_cyclus,'YYYYMMDD') as ingangsdatum_cyclus
      ,      to_char(einddatum_cyclus,'YYYYMMDD')    as einddatum_cyclus
      ,      to_char(opvoerdatum,'YYYYMMDDHH24MMSS')   as opvoerdatum
      ,      objectcyclusnr
      ,      indauthentiek
      ,      indgeconstateerd
      ,      indinonderzoek
      ,      naam
      from   gegmag.gvi_pand_data pnd
      join   gegmag.gvi_pand pdm on (pnd.pnd_id=pdm.id)
    ORACLE_SPATIAL_QUERY_FEATURE_TYPES_FOR_MERGE_FILTERS = Yes
    ORACLE_SPATIAL_SERVER_TYPE = ORACLE8i
    EXPOSED_ATTRIBUTE_LIST = BAG_IDENTIFICATIECODE,PND_ID,BBK_ID,OORSPRONKELIJK_BOUWJAAR,STATUSCODE,LAAGSTE_BOUWLAAG,HOOGSTE_BOUWLAAG,INGANGSDATUM_CYCLUS,EINDDATUM_CYCLUS,OPVOERDATUM,OBJECTCYCLUSNR,INDAUTHENTIEK,INDGECONSTATEERD,INDINONDERZOEK,NAAM
    ORACLE_SPATIAL_REMOVE_SCHEMA_QUALIFIER = NO
    ORACLE_SPATIAL_NAMED_CONNECTION = DBIGMP01
    RESULT -> GeometryExtractor_pand
GeometryExtractor_pand
    KIND_LONG = OGC Well Known Text
    OGC_WKT_PRECISION_DISPLAY = Shortened 64-bit
    REMOVE_GEOMETRY = Yes
    ATTR = geometrie_wkt
    OGCVERSION = 1.1
    -> pand (writer CSV_1)
Note: pand: BAG_compleet [CSV]
pand (writer CSV_1)
    attributes: BAG_IDENTIFICATIECODE auto, PND_ID auto, BBK_ID auto, GEOMETRIE_WKT auto, OORSPRONKELIJK_BOUWJAAR auto, STATUSCODE auto, LAAGSTE_BOUWLAAG auto, HOOGSTE_BOUWLAAG auto, INGANGSDATUM_CYCLUS auto, EINDDATUM_CYCLUS auto, OPVOERDATUM auto, OBJECTCYCLUSNR auto, INDAUTHENTIEK auto, INDGECONSTATEERD auto, INDINONDERZOEK auto, NAAM auto
Note: SQLCreator_pand_verblijfsobject
SQLCreator_pand_verblijfsobject
    DATASET = DBIGMP01
    FORMAT = ORACLE_SPATIAL
    ORACLE_SPATIAL_PERSISTENT_CONNECTION = YES
    COORDSYS = EPSG:28992
    ORACLE_SPATIAL_USE_UNIFIED_DATE_ATTRS = YES
    ORACLE_SPATIAL_SHOW_SYSTEM_TABLES = NO
    SQL_STATEMENT:
      select id
      ,      pnd_id
      ,      vot_id
      ,      to_char(ingangsdatum_geldigheid,'YYYYMMDD') as ingangsdatum_geldigheid
      ,      to_char(einddatum_geldigheid,'YYYYMMDD')    as einddatum_geldigheid
      from   gegmag.gvi_pnd_vot
    ORACLE_SPATIAL_QUERY_FEATURE_TYPES_FOR_MERGE_FILTERS = Yes
    ORACLE_SPATIAL_SERVER_TYPE = ORACLE8i
    EXPOSED_ATTRIBUTE_LIST = ID,PND_ID,VOT_ID,EINDDATUM_GELDIGHEID,INGANGSDATUM_GELDIGHEID
    ORACLE_SPATIAL_REMOVE_SCHEMA_QUALIFIER = NO
    ORACLE_SPATIAL_NAMED_CONNECTION = DBIGMP01
    RESULT -> pand_verblijfsobject (writer CSV_1)
Note: pand_verblijfsobject: BAG_compleet [CSV]
pand_verblijfsobject (writer CSV_1)
    attributes: ID auto, PND_ID auto, VOT_ID auto, EINDDATUM_GELDIGHEID auto, INGANGSDATUM_GELDIGHEID auto
Note: SQLCreator_ligplaats
SQLCreator_ligplaats
    DATASET = DBIGMP01
    FORMAT = ORACLE_SPATIAL
    ORACLE_SPATIAL_PERSISTENT_CONNECTION = YES
    COORDSYS = EPSG:28992
    ORACLE_SPATIAL_USE_UNIFIED_DATE_ATTRS = YES
    ORACLE_SPATIAL_SHOW_SYSTEM_TABLES = NO
    SQL_STATEMENT:
      select
      	to_number(lpsm.bag_identificatiecode) as bag_identificatiecode,
      	to_number(lps.lps_id) as lps_id,
      	to_number(lps.brt_id) as brt_id,
      	lps.geometrie,
          to_char(lps.ingangsdatum_cyclus,'YYYYMMDD') as ingangsdatum_cyclus,
          to_char(lps.einddatum_cyclus,'YYYYMMDD')    as einddatum_cyclus,
      	to_char(opvoerdatum,'YYYYMMDDHH24MMSS')     as opvoerdatum,
      	lps.objectcyclusnr,
      	lps.indauthentiek,
      	lps.indgeconstateerd,
      	lps.indinonderzoek
      from
      	 gegmag.gvi_ligplaats_data lps
      join gegmag.gvi_ligplaats     lpsm on (lps.lps_id=lpsm.id)
    ORACLE_SPATIAL_QUERY_FEATURE_TYPES_FOR_MERGE_FILTERS = Yes
    ORACLE_SPATIAL_SERVER_TYPE = ORACLE8i
    EXPOSED_ATTRIBUTE_LIST = BAG_IDENTIFICATIECODE,BRT_ID,EINDDATUM_CYCLUS,INDAUTHENTIEK,INDGECONSTATEERD,INDINONDERZOEK,INGANGSDATUM_CYCLUS,LPS_ID,OBJECTCYCLUSNR,OPVOERDATUM
    ORACLE_SPATIAL_REMOVE_SCHEMA_QUALIFIER = NO
    ORACLE_SPATIAL_NAMED_CONNECTION = DBIGMP01
    RESULT -> GeometryExtractor_ligplaats
GeometryExtractor_ligplaats
    KIND_LONG = OGC Well Known Text
    OGC_WKT_PRECISION_DISPLAY = Shortened 64-bit
    REMOVE_GEOMETRY = Yes
    ATTR = geometrie_wkt
    OGCVERSION = 1.1
    -> ligplaats (writer CSV_1)
Note: ligplaats: BAG_compleet [CSV]
ligplaats (writer CSV_1)
    attributes: BAG_IDENTIFICATIECODE auto, LPS_ID auto, BRT_ID auto, geometrie_wkt auto, INGANGSDATUM_CYCLUS auto, EINDDATUM_CYCLUS auto, OPVOERDATUM auto, OBJECTCYCLUSNR auto, INDAUTHENTIEK auto, INDGECONSTATEERD auto, INDINONDERZOEK auto
Note: SQLCreator_standplaats
SQLCreator_standplaats
    DATASET = DBIGMP01
    FORMAT = ORACLE_SPATIAL
    ORACLE_SPATIAL_PERSISTENT_CONNECTION = YES
    COORDSYS = EPSG:28992
    ORACLE_SPATIAL_USE_UNIFIED_DATE_ATTRS = YES
    ORACLE_SPATIAL_SHOW_SYSTEM_TABLES = NO
    SQL_STATEMENT:
      select
      	spsm.bag_identificatiecode as bag_identificatiecode,
      	to_number(sps.sps_id) as sps_id,
      	to_number(sps.brt_id)  as brt_id,
      	sps.geometrie,
          to_char(sps.ingangsdatum_cyclus,'YYYYMMDD') as ingangsdatum_cyclus,
          to_char(sps.einddatum_cyclus,'YYYYMMDD')    as einddatum_cyclus,
      	to_char(opvoerdatum,'YYYYMMDDHH24MMSS')     as opvoerdatum,
      	sps.objectcyclusnr,
      	sps.indauthentiek,
      	sps.indgeconstateerd,
      	sps.indinonderzoek
      from
      	 gegmag.gvi_standplaats_data sps
      join gegmag.gvi_standplaats     spsm on (sps.sps_id=spsm.id)
    ORACLE_SPATIAL_QUERY_FEATURE_TYPES_FOR_MERGE_FILTERS = Yes
    ORACLE_SPATIAL_SERVER_TYPE = ORACLE8i
    EXPOSED_ATTRIBUTE_LIST = BAG_IDENTIFICATIECODE,BRT_ID,EINDDATUM_CYCLUS,INDAUTHENTIEK,INDGECONSTATEERD,INDINONDERZOEK,INGANGSDATUM_CYCLUS,OBJECTCYCLUSNR,OPVOERDATUM,SPS_ID
    ORACLE_SPATIAL_REMOVE_SCHEMA_QUALIFIER = NO
    ORACLE_SPATIAL_NAMED_CONNECTION = DBIGMP01
    RESULT -> GeometryExtractor_standplaats
GeometryExtractor_standplaats
    KIND_LONG = OGC Well Known Text
    OGC_WKT_PRECISION_DISPLAY = Shortened 64-bit
    REMOVE_GEOMETRY = Yes
    ATTR = geometrie_wkt
    OGCVERSION = 1.1
    -> standplaats (writer CSV_1)
Note: standplaats: BAG_compleet [CSV]
standplaats (writer CSV_1)
    attributes: BAG_IDENTIFICATIECODE auto, SPS_ID auto, BRT_ID auto, geometrie_wkt auto, INGANGSDATUM_CYCLUS auto, EINDDATUM_CYCLUS auto, OPVOERDATUM auto, OBJECTCYCLUSNR auto, INDAUTHENTIEK auto, INDGECONSTATEERD auto, INDINONDERZOEK auto
Note: SQLCreator_koppel_num_vbo
SQLCreator_koppel_num_vbo
    ORACLE_NONSPATIAL_REMOVE_SCHEMA_QUALIFIER = NO
    DATASET = DBIGMP01
    FORMAT = ORACLE_NONSPATIAL
    ORACLE_NONSPATIAL_PERSISTENT_CONNECTION = YES
    ORACLE_NONSPATIAL_SHOW_SYSTEM_TABLES = NO
    ORACLE_NONSPATIAL_QUERY_FEATURE_TYPES_FOR_MERGE_FILTERS = Yes
    SQL_STATEMENT:
      select
      	to_number(vtm.bag_identificatiecode) as lv_bag_vot_id,
      	to_number(mnum.bag_identificatiecode) as lv_bag_nag_id,
      	aos.vot_id,
      	aos.nag_id,
      	aos.ind_hoofdadres,
      	to_char(aos.ingangsdatum_geldigheid,'YYYYMMDD') as geldig_op,
      	to_char(aos.opvoerdatum,'YYYYMMDDHH24MMSS') as kennisgegeven_op
      from
      	gegmag.gvi_objectadres aos
      join
      	gegmag.gvi_verblijfsobject_data vot
      on
      	aos.vot_id = vot.vot_id
      join
      	gegmag.gvi_verblijfsobject vtm
      on
      	aos.vot_id = vtm.id
      join
      	gegmag.gvi_nummeraanduiding mnum
      on
      	aos.nag_id = mnum.id
    ORACLE_NONSPATIAL_USE_UNIFIED_DATE_ATTRS = YES
    EXPOSED_ATTRIBUTE_LIST = LV_BAG_VOT_ID,LV_BAG_NAG_ID,VOT_ID,NAG_ID,IND_HOOFDADRES,GELDIG_OP,KENNISGEGEVEN_OP
    ORACLE_NONSPATIAL_SERVER_TYPE = ORACLE8i
    ORACLE_NONSPATIAL_NAMED_CONNECTION = DBIGMP01
    RESULT -> bag_koppel_num_vbo (writer CSV_1)
Note: bag_koppel_num_vbo: bag_20171009 [CSV]
bag_koppel_num_vbo (writer CSV_1)
    attributes: LV_BAG_VOT_ID text, LV_BAG_NAG_ID text, VOT_ID text, NAG_ID text, IND_HOOFDADRES text, GELDIG_OP auto, KENNISGEGEVEN_OP auto
Note: SQLCreator_koppel_num_lig
SQLCreator_koppel_num_lig
    ORACLE_NONSPATIAL_REMOVE_SCHEMA_QUALIFIER = NO
    DATASET = DBIGMP01
    FORMAT = ORACLE_NONSPATIAL
    ORACLE_NONSPATIAL_PERSISTENT_CONNECTION = YES
    ORACLE_NONSPATIAL_SHOW_SYSTEM_TABLES = NO
    ORACLE_NONSPATIAL_QUERY_FEATURE_TYPES_FOR_MERGE_FILTERS = Yes
    SQL_STATEMENT:
      select
      	to_number(lpm.bag_identificatiecode) as lv_bag_lps_id,
      	to_number(mnum.bag_identificatiecode) as lv_bag_nag_id,
      	aos.nag_id,
      	aos.lps_id,
      	aos.ind_hoofdadres,
      	to_char(aos.ingangsdatum_geldigheid,'YYYYMMDD') as geldig_op,
      	to_char(aos.opvoerdatum,'YYYYMMDDHH24MMSS') as kennisgegeven_op
      from
      	gegmag.gvi_objectadres aos
      join
      	gegmag.gvi_ligplaats_data lps
      on
      	aos.lps_id = lps.lps_id
      join
      	gegmag.gvi_ligplaats lpm
      on
      	aos.lps_id = lpm.id
      join
      	gegmag.gvi_nummeraanduiding mnum
      on
      	aos.nag_id = mnum.id
    ORACLE_NONSPATIAL_USE_UNIFIED_DATE_ATTRS = YES
    EXPOSED_ATTRIBUTE_LIST = LV_BAG_LPS_ID,LV_BAG_NAG_ID,LPS_ID,NAG_ID,IND_HOOFDADRES,GELDIG_OP,KENNISGEGEVEN_OP
    ORACLE_NONSPATIAL_SERVER_TYPE = ORACLE8i
    ORACLE_NONSPATIAL_NAMED_CONNECTION = DBIGMP01
    RESULT -> bag_koppel_num_lps (writer CSV_1)
Note: bag_koppel_num_lps: bag_20171009 [CSV]
bag_koppel_num_lps (writer CSV_1)
    attributes: LV_BAG_LPS_ID auto, LV_BAG_NAG_ID text, LPS_ID auto, NAG_ID text, IND_HOOFDADRES text, GELDIG_OP auto, KENNISGEGEVEN_OP auto
SQLCreator_koppel_num_sta
    ORACLE_NONSPATIAL_REMOVE_SCHEMA_QUALIFIER = NO
    DATASET = DBIGMP01
    FORMAT = ORACLE_NONSPATIAL
    ORACLE_NONSPATIAL_PERSISTENT_CONNECTION = YES
    ORACLE_NONSPATIAL_SHOW_SYSTEM_TABLES = NO
    ORACLE_NONSPATIAL_QUERY_FEATURE_TYPES_FOR_MERGE_FILTERS = Yes
    SQL_STATEMENT:
      select
      	to_number(spm.bag_identificatiecode) as lv_bag_sps_id,
      	to_number(mnum.bag_identificatiecode) as lv_bag_nag_id,
      	aos.nag_id,
      	aos.sps_id,
      	aos.ind_hoofdadres,
      	to_char(aos.ingangsdatum_geldigheid,'YYYYMMDD') as geldig_op,
      	to_char(aos.opvoerdatum,'YYYYMMDDHH24MMSS') as kennisgegeven_op
      from
      	gegmag.gvi_objectadres aos
      join
      	gegmag.gvi_standplaats_data sps
      on
      	aos.sps_id = sps.sps_id
      join
      	gegmag.gvi_standplaats spm
      on
      	aos.sps_id = spm.id
      join
      	gegmag.gvi_nummeraanduiding mnum
      on
      	aos.nag_id = mnum.id
    ORACLE_NONSPATIAL_USE_UNIFIED_DATE_ATTRS = YES
    EXPOSED_ATTRIBUTE_LIST = LV_BAG_SPS_ID,LV_BAG_NAG_ID,SPS_ID,NAG_ID,IND_HOOFDADRES,GELDIG_OP,KENNISGEGEVEN_OP
    ORACLE_NONSPATIAL_SERVER_TYPE = ORACLE8i
    ORACLE_NONSPATIAL_NAMED_CONNECTION = DBIGMP01
    RESULT -> bag_koppel_num_sps (writer CSV_1)
bag_koppel_num_sps (writer CSV_1)
    attributes: LV_BAG_SPS_ID auto, LV_BAG_NAG_ID text, SPS_ID auto, NAG_ID text, IND_HOOFDADRES text, GELDIG_OP auto, KENNISGEGEVEN_OP auto
